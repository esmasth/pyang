module _3gpp-common-trace {
  yang-version 1.1;
  namespace "urn:3gpp:sa5:_3gpp-common-trace";
  prefix "trace3gpp";

  import _3gpp-common-top { prefix top3gpp; }
  import _3gpp-common-yang-types {prefix types3gpp; }
  import _3gpp-common-yang-extensions {prefix yext3gpp; }
  import ietf-inet-types { prefix inet; }
  import _3gpp-common-files { prefix files3gpp; }

  organization "3GPP SA5";
  contact "https://www.3gpp.org/DynaReport/TSG-WG--S5--officials.htm?Itemid=464";

  description "Trace handling
    Copyright 2023, 3GPP Organizational Partners (ARIB, ATIS, CCSA, ETSI, TSDSI, 
    TTA, TTC). All rights reserved.";
  reference "3GPP TS 28.623
      Generic Network Resource Model (NRM)
      Integration Reference Point (IRP);
      Solution Set (SS) definitions

      3GPP TS 28.622
      Generic Network Resource Model (NRM)
      Integration Reference Point (IRP);
      Information Service (IS)" ;

  revision 2024-01-29 { reference "CR-0316"; }
  revision 2023-11-06 { reference "CR-0290 CR-0294"; }
  revision 2023-11-03 { reference CR-0302 ; } 
  revision 2023-09-18 { reference CR-0271 ; } 
  revision 2023-08-10 { reference CR-0261; }
  revision 2023-04-26 { reference CR-0250; }
  revision 2023-02-18 { reference "CR-0234"; }
  revision 2023-02-16 { reference "CR-0233"; }
  revision 2022-09-30 { reference CR-0191 ; }
  revision 2022-04-27 { reference "CR-0159"; }
  revision 2021-10-18 { reference "CR-0139"; }
  revision 2021-07-22 { reference "CR-0137"; }
  revision 2021-01-25 { reference "CR-0122"; }
  revision 2020-11-16 { reference "CR-0117"; }
  revision 2020-08-06 { reference "CR-0102"; }

  feature FilesUnderTraceJob {
    description "Files shall be contained under TraceJob";
  }

  grouping FreqInfoGrp {
    description "Represents the FreqInfo dataType. 
      This <<dataType>> defines the RF reference frequency and the frequency 
      operating bands used in a cell for a given direction (UL or DL) in FDD 
      or for both UL and DL directions in TDD";
    
    leaf arfcn {
      type uint32 {
        range 0..3279165;
      }
      mandatory true;
      description "RF Reference Frequency as defined in TS 38.104, 
        clause 5.4.2.1. The frequency provided identifies the absolute 
        frequency position of the reference resource block (Common RB 0) 
        of the carrier. Its lowest subcarrier is also known as Point A.";
    }
    
    leaf-list freqBands {
      type uint32 {
        range 1..1024;
      } 
      min-elements 1;
      description "List of NR frequency operating bands. Primary NR 
        Operating Band as defined in TS 38.104, clause 5.4.2.3.
        The value 1 corresponds to n1, value 2 corresponds to NR operating 
        band n2, etc.";
    }
  }
  
  grouping AreaConfigGrp {
    description "Represents the AreaConfig dataType.
      This <<dataType>> defines the area for which measurement logging should 
      be performed. It is described by a list of cells and a list of 
      frequencies.";
    
    list freqInfo {
      key arfcn;
      min-elements 1;
      max-elements 32;
      description "It specifies the carrier frequency and bands used in 
        a cell.";

      uses FreqInfoGrp ;
    }
    
    leaf-list pciList {
      type uint32 {
        range 0..1007;
      } 
      min-elements 1;
      max-elements 32;
      description "List of neighbour cells subject for MDT scope.";
    }
  }
  
  grouping AreaScopeGrp {
    description "Represents the AreaScope dataType.
      This <<dataType>> defines the area scope of MDT.
      The Area Scope parameter in LTE and NR is either:
      - list of Cells, identified by E-UTRAN-CGI or NG-RAN CGI. 
      Maximum 32 CGI can be defined.
      - list of Tracking Area, identified by TAC. 
      Maximum of 8 TAC can be defined. 
      - list of Tracking Area Identity, identified by TAC with 
      associated plmn-Identity perTAC-List containing the 
      PLMN identity for each TAC. Maximum of 8 TAI can be defined.
      The Area Scope parameter in NR can also contain:
      - list of NPN-IDs in NR. It is either a list of PNI-NPNs 
      identified by CAG ID with associated plmn-Identity or a  
      list of SNPNs identified by Network ID with associated 
      plmn-Identity .";    

    choice AreaScopeChoice {
      leaf-list eutraCellIdList {
        type string;
        min-elements 1;
        max-elements 32;
        description "List of E-UTRAN cells identified by E-UTRAN-CGI";
      }
      
      leaf-list utraCellIdList {
        type string;
        min-elements 1;
        max-elements 32;
        description "List of UTRAN cells identified by UTRAN CGI";
      }
      
      leaf-list tacList {
        type types3gpp:Tac;
        min-elements 1;
        max-elements 8;
        description "Tracking Area Code list";
      }
      
      list taiList {
        description "Tracking Area Identity list";
        key idx;
        min-elements 1;
        max-elements 8;
        leaf idx { type string; }
        uses types3gpp:TaiGrp;
      }
    }

    list nPNIdentityList {
      description "list of NPN IDs of in NR. It is either a list of PNI-NPNs 
        identified by CAG ID with associated plmn-Identity or a list of SNPN 
        identified by Network ID with associated plmn-Identity";
      key idx;
      min-elements 1;
      uses NpnIdGrp;
      leaf idx { type string; }
    }
  }
  
  grouping NpnIdGrp {
    description "Represents the NpnId dataType."; 

    list plmnId {
      key "mcc mnc";
      description "It specifies the PLMN Id of the NPN network.";
      uses types3gpp:PLMNId;
      max-elements 1;
    }

    list cAGIdList {
      key idx;
      max-elements 256;
      description "It specifies the PNI-NPN identified by CAG ID ";
      leaf idx { type string; }
    }

    list nIDList {
      key idx;
      max-elements 16;
      description "It specifies the SNPN identified by Network ID";
      leaf idx { type string; }
    }
  }

  grouping ExcessPacketDelayThresholdsGrp {
    description "Represents the ExcessPacketDelayThresholds dataType.
      This <<dataType>> defines a excess packet delay threshold information 
      to enable the calculation of the PDCP Excess Packet Delay in the 
      uplink in case of M6 uplink measurements are requested. The excess 
      packet delay threshold information is specified with the 5QI value 
      and excess packet delay threshold value.";
    
    leaf fiveQIValue {
      type uint8;
      mandatory true;
      description "It indicates 5QI value.";
    }
    
    leaf excessPacketDelayThresholdValue {
      type decimal64 {
        fraction-digits 2;
        range 0.25|0.5|1|2|4|5|10|20|30|40|50|60|70|80|90|100|150|300|500 ;
      }
      mandatory true;
      units milliseconds;
      description "Value of excess packet delay threshold 
        for M6 UL measurement in milliseconds.";
    }
  }
  
  grouping TraceReferenceGrp {
    description "Represents the TraceReference dataType.
      This <<dataType>> defines a globally unique identifier, which uniquely 
      identifies the Trace Session that is created by the TraceJob. It is 
      composed of the MCC, MNC (resulting in PLMN identifier) and the 
      trace identifier.";
    
      uses types3gpp:PLMNId;  // mcc+mnc
      
      leaf traceId {
        type string;
        mandatory true;
        description "An identifier, which identifies the Trace 
          (together with MCC and MNC). This is a 3 byte Octet String.";
      }
  }
  
  grouping MbsfnAreaGrp {
    description "Represents the MbsfnArea dataType. 
      This <<dataType>> defines a MBSFN area. It is composed of the MBSFN Area 
      identifier and the carrier frequency (EARFCN).";
  
    leaf mbsfnAreaId {
      type uint32 {
        range 1..max;
      }
      mandatory true;
      description "MBSFN Area Identifier";
    }
    
    leaf earfcn{
      type uint32 {
        range 1..max;
      }
      mandatory true;
      description "Carrier Frequency";
    }

    list nPNIdentityList {
       description "list of NPN IDs of in NR. It is either a list of PNI-NPNs 
        identified by CAG ID with associated plmn-Identity or a list of SNPN 
        identified by Network ID with associated plmn-Identity";
      key idx;
      min-elements 1;  
      uses NpnIdGrp;
      leaf idx { type string; }
    }
  }
  
  grouping TraceConfigGrp {

   description "Defines the configuration parameters of TraceJob 
     which are specific for Trace or combined Trace and Immediate MDT.
     The attribute listOfNeTypes specifies the network elements to be 
     traced. The optional attribute listOfInterfaces allows to specify
     the individual interfaces of the network elements to be recorded.
     The attribute traceDepth allows to configure the level of detail 
     of the information which shall be recorded.  For trace the reporting
     is event based, where the triggering event is configured with 
     attribute triggeringEvent. For each triggering event the first and 
     last message (start/stop triggering event) to record  are specified.";

  list listOfInterfaces {
      key idx;

      description "Specifies the interfaces that need to be traced in the given
        ManagedEntityFunction.The attribute is applicable only for Trace. In
        case this attribute is not used, it carries a null semantic.";
      reference "Clause 5.5 of 3GPP TS 32.422 for additional details on the
        allowed values.";

      leaf idx { type uint32 ; }

      leaf-list MSCServerInterfaces {
        type enumeration {
          enum A ;
          enum Iu-CS ;
          enum Mc ;
          enum MAP-G ;
          enum MAP-B ;
          enum MAP-E ;
          enum MAP-F ;
          enum MAP-D ;
          enum MAP-C ;
          enum CAP ;
        }
      }
      leaf-list MGWInterfaces {
        type enumeration {
          enum Mc ;
          enum Nb-UP ;
          enum Iu-UP ;
        }
      }
      leaf-list RNCInterfaces {
        type enumeration {
          enum Iu-CS ;
          enum Iu-PS ;
          enum Iur ;
          enum Iub ;
          enum Uu ;
        }
      }
      leaf-list SGSNInterfaces {
        type enumeration {
          enum Gb ;
          enum Iu-PS ;
          enum Gn ;
          enum MAP-Gr ;
          enum MAP-Gd ;
          enum MAP-Gf ;
          enum Ge ;
          enum Gs ;
          enum S6d ;
          enum S4 ;
          enum S3 ;
          enum S13 ;
        }
      }
      leaf-list GGSNInterfaces {
        type enumeration {
          enum Gn ;
          enum Gi ;
          enum Gmb ;
        }
      }
      leaf-list S-CSCFInterfaces {
        type enumeration {
          enum Mw ;
          enum Mg ;
          enum Mr ;
          enum Mi ;
        }
      }
      leaf-list P-CSCFInterfaces {
        type enumeration {
          enum Gm ;
          enum Mw ;
        }
      }
      leaf-list I-CSCFInterfaces {
        type enumeration {
          enum Cx ;
          enum Dx ;
          enum Mg ;
          enum Mw ;
        }
      }
      leaf-list MRFCInterfaces {
        type enumeration {
          enum Mp ;
          enum Mr ;
        }
      }
      leaf-list MGCFInterfaces {
        type enumeration {
          enum Mg ;
          enum Mj ;
          enum Mn ;
        }
      }
      leaf-list IBCFInterfaces {
        type enumeration {
          enum Ix ;
          enum Mx ;
        }
      }
      leaf-list E-CSCFInterfaces {
        type enumeration {
          enum Mw ;
          enum Ml ;
          enum Mm ;
          enum Mi-Mg ;
        }
      }
      leaf-list BGCFInterfaces {
        type enumeration {
          enum Mi ;
          enum Mj ;
          enum Mk ;
        }
      }
      leaf-list ASInterfaces {
        type enumeration {
          enum Dh ;
          enum Sh ;
          enum ISC ;
          enum Ut ;
        }
      }
      leaf-list HSSInterfaces {
        type enumeration {
          enum MAP-C ;
          enum MAP-D ;
          enum Gc ;
          enum Gr ;
          enum Cx ;
          enum S6d ;
          enum S6a ;
          enum Sh ;
        }
      }
      leaf-list EIRInterfaces {
        type enumeration {
          enum MAP-F ;
          enum S13 ;
          enum MAP-Gf ;
        }
      }
      leaf-list BM-SCInterfaces {
        type enumeration {
          enum Gmb ;
        }
      }
      leaf-list MMEInterfaces {
        type enumeration {
          enum S1-MME ;
          enum S3 ;
          enum S6a ;
          enum S10 ;
          enum S11 ;
          enum S13 ;
        }
      }
      leaf-list SGWInterfaces {
        type enumeration {
          enum S4 ;
          enum S5 ;
          enum S8 ;
          enum S11 ;
          enum Gxc ;
        }
      }
      leaf-list PDN_GWInterfaces {
        type enumeration {
          enum S2a ;
          enum S2b ;
          enum S2c ;
          enum S5 ;
          enum S6b ;
          enum Gx ;
          enum S8 ;
          enum SGi ;
        }
      }
      leaf-list eNBInterfaces {
        type enumeration {
          enum S1-MME ;
          enum X2 ;
        }
      }
      leaf-list en-gNBInterfaces {
        type enumeration {
          enum S1-MME ;
          enum X2 ;
          enum Uu ;
          enum F1-C ;
          enum E1 ;
        }
      }
      leaf-list AMFInterfaces {
        type enumeration {
          enum N1 ;
          enum N2 ;
          enum N8 ;
          enum N11 ;
          enum N12 ;
          enum N14 ;
          enum N15 ;
          enum N20 ;
          enum N22 ;
          enum N26 ;
        }
      }
      leaf-list AUSFInterfaces {
        type enumeration {
          enum N12 ;
          enum N13 ;
        }
      }
      leaf-list NEFInterfaces {
        type enumeration {
          enum N29 ;
          enum N30 ;
          enum N33 ;
        }
      }
      leaf-list NRFInterfaces {
        type enumeration {
          enum N27 ;
        }
      }
      leaf-list NSSFInterfaces {
        type enumeration {
          enum N22 ;
          enum N31 ;
        }
      }
      leaf-list PCFInterfaces {
        type enumeration {
          enum N5 ;
          enum N7 ;
          enum N15 ;
        }
      }
      leaf-list SMFInterfaces {
        type enumeration {
          enum N4 ;
          enum N7 ;
          enum N10 ;
          enum N11 ;
          enum S5-C ;
          enum N38 ;
          enum N16 ;
          enum N16a ;
        }
      }
      leaf-list SMSFInterfaces {
        type enumeration {
          enum N20 ;
          enum N21 ;
        }
      }
      leaf-list UDMInterfaces {
        type enumeration {
          enum N8 ;
          enum N10 ;
          enum N13 ;
          enum N21 ;
        }
      }
      leaf-list UPFInterfaces {
        type enumeration {
          enum N4 ;
        }
      }
      leaf-list ng-eNBInterfaces {
        type enumeration {
          enum NG-C ;
          enum Xn-C ;
          enum Uu ;
        }
      }
      leaf-list gNB-CU-CPInterfaces {
        type enumeration {
          enum NG-C ;
          enum Xn-C ;
          enum Uu ;
          enum F1-C ;
          enum E1 ;
          enum X2-C ;
        }
      }
      leaf-list gNB-CU-UPInterfaces {
        type enumeration {
          enum E1 ;
        }
      }
      leaf-list gNB-DUInterfaces {
        type enumeration {
          enum F1-C ;
      }
    }
    }

    leaf-list listOfNETypes {
      type enumeration {
        enum MSC_SERVER;
        enum SGSN;
        enum MGW;
        enum GGSN;
        enum RNC;
        enum BM_SC;
        enum MME;
        enum SGW;
        enum PGW;
        enum ENB;
        enum EN_GNB;
        enum GNB_CU_CP;
        enum GNB_CU_UP;
        enum GNB_DU;
      }
      description "Specifies in which type of ManagedFunction the trace should
        be activated. The attribute is applicable only for Trace with
        Signalling Based Trace activation. In case this attribute is not used,
        it carries a null semantic";
      reference "Clause 5.4 of 3GPP TS 32.422 for additional details on the
        allowed values";
    }

    leaf traceDepth {
      when '../../jobType = "TRACE_ONLY"'
        +  ' or ../../jobType = "IMMEDIATE_MDT_AND_TRACE"';
      type enumeration  {
        enum MINIMUM;
        enum MEDIUM;
        enum MAXIMUM;
        enum VENDORMINIMUM;
        enum VENDORMEDIUM;
        enum VENDORMAXIMUM;
      }
      default MAXIMUM;
      description "Specifies how detailed information should be recorded in the
        Network Element. The Trace Depth is a paremeter for Trace Session level,
        i.e., the Trace Depth is the same for all of the NEs to be traced in
        the same Trace Session.
        The attribute is applicable only for Trace, otherwise it carries a null
        semantic.";
      reference "Clause 5.3 of 3GPP TS 32.422";
    }  
  }

  grouping ImmediateMdtConfigGrp {
   description "Represents the ImmediateMdtConfig dataType. 
      This <<dataType>> defines the configuration parameters of 
      IOC TraceJob which are specific for Immediate MDT or combine 
      Trace and Immediate MDT. 
      
      The optional attribute positioningMethod allows to specify 
      the positioning methods to use.

      The following attributes are conditional available based on the
      measurements configured in listOfMeasurements:
        -reportInterval: conditional for M1 in LTE or NR and M1/M2 in UMTS,
        -reportAmount: conditional for M1 in LTE or NR and M1/M2 in UMTS,
        -reportingTrigger: conditional for M1 in LTE or NR and M1/M2 in UMTS,
        -eventThreshold: conditional for A2 event reporting or A2 event
          triggered periodic reporting,
        -collectionPeriodRrmNR: conditional for M4 and M5 in NR,
        -collectionPeriodM6NR: conditional for M6 in NR,
        -collectionPeriodM7NR: conditional for M7 in NR,
        -collectionPeriodRrmLte (conditional for M3 in LTE),
        -measurementPeriodLTE (conditional for M4 and M5 in LTE),
        -collectionPeriodM6Lte (conditional for M6 in LTE),
        -collectionPeriodM7Lte (conditional for M7 in LTE),
        -collectionPeriodRrmUmts (conditional for M4 and M5 in UMTS),
        -measurementPeriodUmts (conditional for M6 and M7 in UMTS),
        -measurementQuantity (conditional for 1F event reporting),
        -beamLevelMeasurement (conditional for M1 in NR),
        -excessPacketDelayThresholds (conditional for M6 UL measurement in NR).

       For immediate MDT, the measurement reporting is dependent on the 
       configured measurements:
        
        - For measurement M1 in LTE or NR, it is possible to select between 
        periodical, event triggered, event triggered periodic reporting or 
        reporting according to all configured RRM event triggers. For M1 and M2 
        measurement in UMTS, it is possible to select between periodical, event 
        triggered reporting or reporting according to all configured RRM event 
        triggers. Parameter reportingTrigger determines which of the reporting 
        methods is selected and in case of event triggered or event-triggered 
        periodic, which is the decisive event type. For periodical reporting, 
        parameters reportInterval and reportAmount determine the interval between
        two successive reports and the number of reports. This means the 
        periodical reporting terminates after reportAmount reports have been
        sent as long as reportAmount is configured with a value different from 
        infinity. For event-triggered periodic reporting, these two parameters 
        apply in addition to parameter eventThreshold which determines the 
        threshold of the event. In this case up to reportAmount reports are 
        sent with a periodicity of reportInterval after the entering condition 
        is fulfilled. The reporting is stopped, if the leaving condition is 
        fulfulled and is restarted if the configured event reoccurs. For event 
        based reporting, there is only one report sent after the event occurs. 
        The parameters to configure are reportingTrigger and eventThreshold. 
        In case of UMTS and 1f event reporting, additionally parameter 
        measurementQuantity is necessary in order to determine for which 
        measurement(s) the event threshold is applicable.  Parameter 
        beamLevelMeasurement determines whether beam level measurements shall
        be included in case of NR.
        
        - For measurement M2 in LTE or NR, reporting is according to RRM
        configuration, see TS 38.321, TS 36.321 and TS 38.331, TS 36.331.  
        For measurement M4 in UMTS, reporting is either according to RRM 
        configuration, see TS 25.321 and TS 25.331 or periodic or event
        triggered periodic using parameter collectionPeriodRrmUmts and 
        eventThresholdUphUmts.
        
        - For measurement M3 in UMTS, the reporting is done upon
        availability, see TS 37.320.
        
        - For measurements M4, M5, M6 and M7 in NR, for measurements 
        M3, M4, M5, M6 and M7 in LTE and for measurements M5, M6 and M7 
        in UMTS periodical reporting is applied. The configurable parameter
        is the interval between two measurements (collectionPeriodRrmNr, 
        collectionPeriodM6NR, collectionPeriodM7Nr, collectionPeriodRrmLte,
        measurementPeriodLte, collectionPeriodM6Lte, collectionPeriodM7Lte,
        collectionPeriodRrmUmts, measurementPeriodUmts).  If no collection
        period is configured for M5 in UMTS, all available measurements are
        logged according to RRM configuration.";
        
   leaf listOfMeasurements {
      when 'jobType = "IMMEDIATE_MDT_ONLY"';
      type enumeration {
        enum M1;
        enum M2;
        enum M3;
        enum M4;
        enum M5;
        enum M6_DL;
        enum M6_UL;
        enum M7_DL;
        enum M7_UL;
        enum M1_EVENT_TRIGGERED;
        enum M6;
        enum M7;
        enum M8;
        enum M9;
      }
      description "It specifies the UE measurements that shall be collected in
        an Immediate MDT job. The attribute is applicable only for Immediate MDT.
        In case this attribute is not used, it carries a null semantic.";
      reference "3GPP TS 32.422 clause 5.10.3";
    }

   leaf reportingTrigger {
      when 'jobType = "IMMEDIATE_MDT_ONLY"';
      type enumeration {
        enum PERIODICAL;
        enum A2_FOR_LTE;
        enum 1F_FOR_UMTS;
        enum 1I_FOR_UMTS_MCPS_TDD;
        enum A2_TRIGGERED_PERIODIC_FOR_LTE;
        enum ALL_CONFIGURED_RRM_FOR_LTE;
        enum ALL_CONFIGURED_RRM_FOR_UMTS;
      }
      description "It specifies whether periodic or event based measurements
        should be collected.
        The attribute is applicable only for Immediate MDT and when the
        listOfMeasurements is configured for M1 (for both UMTS and LTE)
        or M2 (only for UMTS). In case this attribute is not used, it carries
        a null semantic.";
      reference "Clause 5.10.4 of 3GPP TS 32.422";
    }

   leaf reportInterval {
      when 'jobType = "IMMEDIATE_MDT_ONLY"'
        +  ' and ../reportingTrigger = "PERIODICAL"';
      type uint32 {
        range "120|240|250|480|500|640|1000|1024|2000|2048|3000|4000|"
          +"5120|6000|8000|10240|12000|16000|20000|"
          +"20480|24000|28000|32000|40960|60000|64000|"
          +"360000|720000|1800000|3600000";
      }
      units milliseconds;
      description "It specifies the interval between the periodical measurements
        that shall be taken when the UE is in connected mode.
        The attribute is applicable only for Immediate MDT and when
        reportingTrigger is configured for periodical measurements. In case
        this attribute is not used, it carries a null semantic.";
      reference "5.10.5 of 3GPP TS 32.422";
    }
    
   leaf reportAmount {
      when 'jobType = "IMMEDIATE_MDT_ONLY"'
        +  ' and ../reportingTrigger = "PERIODICAL"';
      type union {
        type uint32 {
          range "1|4|8|16|32|64" ;
        }
        type enumeration {
          enum INFINITY;
        }
      }
      description "It specifies the number of measurement reports that shall be
        taken for periodic reporting while the UE is in connected.
        The attribute is applicable only for Immediate MDT and when
        reportingTrigger is configured for periodical measurements. In
        case this attribute is not used, it carries a null semantic.";
      reference "Clause 5.10.6 of 3GPP TS 32.422";
    }
    
   leaf eventThreshold {
      when 'jobType = "IMMEDIATE_MDT_ONLY"';
      type int64;
      description "Specifies the threshold which should trigger the reporting
        in case A2 event reporting in LTE or 1F/1l event in UMTS. The attribute
        is applicable only for Immediate MDT and when reportingTrigger is
        configured for A2 event in LTE or 1F event or 1l event in UMTS. In
        case this attribute is not used, it carries a null semantic.";
      reference "Clauses 5.10.7 and 5.10.7a of 3GPP TS 32.422";
    }
    
   leaf collectionPeriodRRMNR {
      when 'jobType = "IMMEDIATE_MDT_ONLY"'
        + ' or jobType = "IMMEDIATE_MDT_AND_TRACE"';
      type uint32 {
        range "1024|2048|5120|10240|60000";
      }
      units milliseconds;
      description "Specifies the collection period for collecting RRM 
        configured measurement samples for M4, M5 in NR. The attribute is 
        applicable only for Immediate MDT. In case this attribute is not 
        used, it carries a null semantic.";
      reference "Clause 5.10.30 of 3GPP TS 32.422";
    }

   leaf collectionPeriodRRMLTE {
      when 'jobType = "IMMEDIATE_MDT_ONLY"' 
        +  ' or jobType = "IMMEDIATE_MDT_AND_TRACE"';
      type uint32 {
        range "250|500|1000|2000|3000|4000|6000|8000|12000|16000|20000|"
          +"24000|28000|32000|64000";
      }
      units milliseconds;
      description "Specifies the collection period for collecting RRM configured
        measurement samples for M2, M3 in LTE. The attribute is applicable only
        for Immediate MDT. In case this attribute is not used, it carries a
        null semantic.";
      reference "Clause 5.10.20 of 3GPP TS 32.422";
    }
    
   leaf collectionPeriodM6NR {
      when 'jobType = "IMMEDIATE_MDT_ONLY"'
        + ' or jobType = "IMMEDIATE_MDT_AND_TRACE"';
      type enumeration {
        enum 120ms;
        enum 240ms;
        enum 480ms;
        enum 640ms;
        enum 1024ms;
        enum 2048ms;
        enum 5120ms;
        enum 10240ms;
        enum 20480ms;
        enum 40960ms;
        enum 1min;
        enum 6min;
        enum 12min;
        enum 30min;
      }
      description "It specifies the collection period for the Packet Delay 
        measurement (M6) for NR MDT taken by the gNB. The attribute is 
        applicable only for Immediate MDT. In case this attribute is not used, 
        it carries a null semantic.";
      reference "clause 5.10.34 of  TS 32.422";
    }
    
    leaf collectionPeriodM7NR {
      when 'jobType = "IMMEDIATE_MDT_ONLY"'
        + ' or jobType = "IMMEDIATE_MDT_AND_TRACE"';
      type uint32 {
        range "1..60";
      }
      description "It specifies the collection period for the Packet Loss Rate 
        measurement (M7) for NR MDT taken by the gNB. The attribute is 
        applicable only for Immediate MDT. In case this attribute is not used, 
        it carries a null semantic.";    
      reference "clause 5.10.35 of  TS 32.422";
    }

    leaf collectionPeriodM6LTE {
      when 'jobType = "IMMEDIATE_MDT_ONLY"' 
        +  ' or jobType = "IMMEDIATE_MDT_AND_TRACE"';
      type uint32 {
        range "1024|2048|5120|10240";
      }
      units milliseconds;
      description "Specifies the collection period for the Packet Delay 
        measurement (M6) for MDT taken by the eNB. The attribute is applicable 
        only for Immediate MDT. In case this attribute is not used, 
        it carries a null semantic.";
      reference "Clause 5.10.32 of  TS 32.422 ";
    }
    
    leaf collectionPeriodM7LTE {
      when 'jobType = "IMMEDIATE_MDT_ONLY"' 
        +  ' or jobType = "IMMEDIATE_MDT_AND_TRACE"';
      type uint16 {
        range 1..60 ;
      }
      description "It specifies the collection period for the Packet Loss Rate 
        measurement (M7) for LTE MDT taken by the eNB. The attribute is 
        applicable only for Immediate MDT. In case this attribute 
        is not used, it carries a null semantic.";
      reference "Clause 5.10.33 of  TS 32.422 .";
    }

    leaf eventThresholdUphUMTS {
      when 'jobType = "IMMEDIATE_MDT_ONLY"' 
        +  ' or jobType = "IMMEDIATE_MDT_AND_TRACE"';
      type uint16 {
        range 0..31 ;
      }        
      description "It specifies the threshold which should trigger 
        the reporting in case of event-triggered periodic reporting for M4 
        (UE power headroom measurement) in UMTS. In case this attribute is 
        not used, it carries a null semantic.";
        reference "5.10.39 of TS 32.422";
    }

    leaf collectionPeriodRRMUMTS {
      when 'jobType = "IMMEDIATE_MDT_ONLY"'
        +  ' or jobType = "IMMEDIATE_MDT_AND_TRACE"';
      type uint32 {
        range "1024|1280|2048|2560|5120|"
          +"10240|60000";
      }
      units milliseconds;
      description "Specifies the collection period for collecting RRM configured
        measurement samples for M3, M4, M5 in UMTS. The attribute is applicable
        only for Immediate MDT. In case this attribute is not used, it carries
        a null semantic";
      reference "Clause 5.10.21 of 3GPP TS 32.422";
    }

   leaf measurementPeriodLTE {
          when 'jobType = "IMMEDIATE_MDT_ONLY"'
            +  ' or jobType = "IMMEDIATE_MDT_AND_TRACE"';
      type uint32 {
        range "1024|1280|2048|2560|5120|"
          +"10240|60000";
      }
      units milliseconds;
      mandatory true;
      description "It specifies the measurement period for the Data Volume and
        Scheduled IP throughput measurements for MDT taken by the eNB.
        The attribute is applicable only for Immediate MDT. In case this
        attribute is not used, it carries a null semantic.";
      reference "Clause 5.10.23 of 3GPP TS 32.422";
    }

    leaf measurementPeriodUMTS {
      when 'jobType = "IMMEDIATE_MDT_ONLY"'
        +  'or jobType = "IMMEDIATE_MDT_AND_TRACE"';
      type uint32 {
        range "250|500|1000|2000|3000|4000|6000|8000|12000|16000|20000|"
          +"24000|28000|32000|64000";
      }
      units milliseconds;
      mandatory true;
      description "It specifies the measurement period for the Data Volume and
        Throughput measurements for MDT taken by RNC.
        The attribute is applicable only for Immediate MDT. In case this
        attribute is not used, it carries a null semantic.";
      reference "Clause 5.10.22 of 3GPP TS 32.422";
    }

    leaf measurementQuantity {
      when 'jobType = "IMMEDIATE_MDT_ONLY"'
        +  ' or jobType = "IMMEDIATE_MDT_AND_TRACE"';
      type enumeration {
        enum CPICH_ECNO;
        enum CPICH_RSCP;
        enum PATHLOSS;
      }
      description "It specifies the measurements that are collected in an MDT
        job for a UMTS MDT configured for event triggered reporting.";
      reference "Clause 5.10.15 of 3GPP TS 32.422";
    }
    
    leaf beamLevelMeasurement {
      when 'jobType = "IMMEDIATE_MDT_ONLY"'
        +  ' or jobType = "IMMEDIATE_MDT_AND_TRACE"';
      type boolean;
      default false;
      description "Indicates whether the NR M1 beam level measurements shall 
        be included or not.";
      reference "Clause 5.10.40 of TS 32.422";
    }

    leaf positioningMethod {
      when 'jobType = "IMMEDIATE_MDT_ONLY"'
        +  ' or jobType = "IMMEDIATE_MDT_AND_TRACE"';
      type enumeration {
        enum GNSS;
        enum E_CELL_ID;
      }
      description "It specifies what positioning method should be used in the
        MDT job.";
      reference "Clause 5.10.19 of 3GPP TS 32.422";
    }
    
    list excessPacketDelayThresholds {
      description "Excess packet delay thresholds info for M6 UL measurement.";
      min-elements 1;
      key idx;
      leaf idx { type string; }
      uses ExcessPacketDelayThresholdsGrp;
    }
  }

  grouping LoggedMdtGrp {
    description "This <<dataType>> defines the configuration parameters of 
    IOC TraceJob which are specific for Logged MDT or Logged MBSFN MDT. 
    The optional attribute plmnList allows to specify the PLMNs where 
    measurement collection, status indication and log reporting is allowed, 
    the optional attribute areaConfigurationForNeighCell allows to specify 
    the area for which UE is requested to perform measurements logging for 
    neighbour cells which have list of frequencies.  For logged MDT in UMTS 
    and LTE, the reporting is periodical. Parameter loggingInterval determines 
    the interval between the reports and parameter loggingDuration determines 
    how long the configuration is valid meaning after this duration has passed 
    no further reports are sent. In NR, the reporting can be periodical or event 
    based, determined by parameter reportType. For periodical reporting the 
    same parameters as in LTE and UMTS apply. For event based reporting, 
    parameter eventListForEventTriggeredMeasurement configures the event type, 
    namely 'out of coverage' or 'L1 event'. In case 'L1 event' is selected as 
    event type, the logging is performed according to parameter loggingInterval
    at regular intervals only when the conditions indicated by eventThresholdL1, 
    hysteresisL1, timeToTriggerL1 (defining the thresholds, hysteresis and time 
    to trigger) are met and if UE is 'camped normally' state (TS 38.331, 
    TS 38.304).  In case 'out of coverage' is selected as event type, the
    logging is performed according to parameter loggingInterval at regular 
    intervals only when the UE is in 'any cell selection' state. 
    Furthermore, logging is performed immediately upon transition from the
    'any cell selection' state to the 'camped normally' state (TS 38.331, 
    TS 38.304).";
    
   leaf traceCollectionEntityIPAddress {
      when '../traceReportingFormat  = "FILE_BASED" or '
        +'jobType = "LOGGED_MDT_ONLY" or jobType = "LOGGED_MBSFN_MDT"';
      type union {
        type inet:uri;
        type inet:ip-address;
      }
      description "Specifies the address of the Trace Collection Entity when
        the attribute traceReportingFormat is configured for the file-based
        reporting. The attribute is applicable for both Trace and MDT.";
      reference "Clause 5.9 of 3GPP TS 32.422";
    }
    
    leaf loggingDuration {
      when 'jobType = "LOGGED_MDT_ONLY" or' 
        + ' jobType = "LOGGED_MBSFN_MDT"';
      type uint32 {
        range "600|1200|2400|3600|5400|7200";
      }
      units seconds;
      description "Specifies how long the MDT configuration is valid at the
        UE in case of Logged MDT. The attribute is applicable only for
        Logged MDT and Logged MBSFN MDT. In case this attribute is not used, it
        carries a null semantic.";
      reference "5.10.9 of 3GPP TS 32.422";
    }

    leaf loggingInterval {
      when 'jobType = "LOGGED_MDT_ONLY" or' 
        + ' jobType = "LOGGED_MBSFN_MDT"';
      type uint32 {
        range "0|320|640|1280|2560|5120|10240|20480|"
          +"30720|40960|61440";
      }
      units milliseconds;
      description "Specifies the periodicty for Logged MDT. The attribute is
        applicable only for Logged MDT and Logged MBSFN MDT. In case this
        attribute is not used, it carries a null semantic.
        The value 0 indicates Infinity for NR.";
      reference "5.10.8 of 3GPP TS 32.422";
    }
    
    leaf reportType {
      when 'jobType = "IMMEDIATE_MDT_ONLY"';
      type enumeration {
        enum PERIODICAL;
        enum EVENT_TRIGGERED;
      }
      description "It specifies report type for logged NR MDT";
      reference "Clause 5.10.27 of 3GPP TS 32.422";
    }
    
    leaf eventListForEventTriggeredMeasurement {
      when 'jobType = "LOGGED_MDT_ONLY"';
      type enumeration {
        enum OUT_OF_COVERAGE ;
        enum A2_EVENT ;
      }
      description "Specifies event types for event triggered measurement in the
        case of logged NR MDT.  Each trace session may configure at most one
        event. The UE shall perform logging of measurements only upon certain
        condition being fulfilled:
        - Out of coverage.
        - A2 event.";
      reference "Clause 5.10.28 of 3GPP TS 32.422";
    }

    leaf eventThresholdL1 {
      when 'jobType = "LOGGED_MDT_ONLY" or' 
        + ' jobType = "LOGGED_MBSFN_MDT"';
      type uint32 {
        range "0..127";
      }
      description "It specifies the threshold which should trigger 
        the reporting in case of event based reporting of logged NR MDT. 
        The attribute is applicable only for Logged MDT and when reportType 
        is configured for event triggered reporting and when 
        eventListForEventTriggeredMeasurement is configured for L1 event. 
        In case this attribute is not used, it carries a null semantic.";
      reference "clause 5.10.36 of TS 32.422";
    }
    
    leaf hysteresisL1 {
      when 'jobType = "LOGGED_MDT_ONLY" or '
         + 'jobType = "LOGGED_MBSFN_MDT"';
      type uint32 {
        range "0..30";
      }
      description "It specifies the hysteresis used within the entry and leave 
        condition of the L1 event based reporting of logged NR MDT. 
        The attribute is applicable only for Logged MDT, when reportType 
        is configured for event triggered reporting and when 
        eventListForEventTriggeredMeasurement is configured for L1 event. 
        In case this attribute is not used, it carries a null semantic.";
      reference "clause 5.10.37 of TS 32.422";
    }

     leaf timeToTriggerL1 {
      when 'jobType = "LOGGED_MDT_ONLY" or '
          + 'jobType = "LOGGED_MBSFN_MDT"';
      type int32 {
        range 0|40|64|80|100|128|160|256|320|480|512|640|1024|1280|2560|5120;
      }
      units milliseconds;
      description "It specifies the threshold which should trigger 
        the reporting in case of event based reporting of logged NR MDT. 
        The attribute is applicable only for Logged MDT, when reportType 
        is configured for event triggered reporting and when 
        eventListForEventTriggeredMeasurement is configured for L1 event. 
        In case this attribute is not used, it carries a null semantic.";
      reference "clauses 5.10.38 of TS 32.422";
    }
    
    list pLMNList {
      when 'jobType = "LOGGED_MDT_ONLY"';
      key "mcc mnc";
      uses types3gpp:PLMNId;
      max-elements 16;
      description "It indicates the PLMNs where measurement collection, status
        indication and log reporting is allowed.";
      reference "Clause 5.10.24 of 3GPP TS 32.422";
    }
    
    list areaConfigurationForNeighCell {
      when 'jobType = "LOGGED_MDT_ONLY"';
      key "idx";
      leaf idx { type uint32 ; }
      description "It specifies the area for which UE is requested to perform
        measurement logging for neighbour cells which have list of frequencies.
        If it is not configured, the UE shall perform measurement logging for
        all the neighbour cells.

        Applicable only to NR Logged MDT.";
      reference "3GPP TS 32.422 clause 5.10.26.";

      uses AreaConfigGrp;
    }

    list mBSFNAreaList {
      when 'jobType = "LOGGED_MBSFN_MDT"';
      key "mbsfnAreaId earfcn";
      max-elements 8;
      description "The MBSFN Area consists of a MBSFN Area ID and Carrier
        Frequency (EARFCN). The target MBSFN area List can have up to 8 entries.
        This parameter is applicable only if the job type is Logged MBSFN MDT.";
      reference "5.10.25 of 3GPP TS 32.422";
      
      uses MbsfnAreaGrp;
    }
  }

  grouping MdtConfigGrp {
    description "Defines the configuration parameters of IOC 
     TraceJob which are specific for MDT. The attribute 
     anonymizationOfMdtData specifies the level of anonymization 
     of MDT data.  The optional attribute areaScope allows to 
     specify the area in terms of cells or Tracking Area/Routing 
     Area/Location area where the MDT data collection shall take 
     place. In case of RLF_REPORT_ONLY and RCEF_REPORT_ONLY the 
     optional attribute areaScope allows to specify the eNB or list 
     of eNBs or gNB or list of gNBs where the reports should be 
     collected.  The optional attribute sensorInformation allows to 
     specify  the sensor information to include.  Based on the value 
     configured for attribute jobType in IOC TraceJob, the attributes 
     immediateMdtConfig or loggedMdtConfig are available: In case of 
     IMMEDIATE_MDT_ONLY or IMMEDIATE_MDT_AND_TRACE the attribute 
     immediateMdtConfig is applicable. In case of LOGGED_MDT_ONLY or 
     LOGGED_MBSFN_MDT the attribute loggedMdtConfig is applicable.";

   leaf anonymizationOfMDTData {
      when ../areaScope ;
      type enumeration {
        enum NO_IDENTITY;
        enum TAC_OF_IMEI;
      }
      default NO_IDENTITY;
      description "Specifies level of MDT anonymization.";
      reference "3GPP TS 32.422 clause 5.10.12.";
    }

   list areaScope {
      key "idx";
      leaf idx { type uint32 ; }
      description "It specifies the area where data shall be collected. 
        List of eNB/list of gNB/eNB/gNB for RLF or RCEF.

        List of cells/TA/LA/RA for signaling based MDT or management 
        based Logged MDT.
  
        List of cells for management based Immediate MDT.

        List of NPN IDs for management based MDT.
  
        Cell, TA, LA, RA are mutually exclusive.
         
        This attribute shall be present if MDT is supported.";
        reference "Clause 5.10.2 of 3GPP TS 32.422";
        
      uses AreaScopeGrp;      
    }

   leaf-list sensorInformation {
      type enumeration {
        enum BAROMETRIC_PRESSURE;
        enum UE_SPEED;
        enum UE_ORIENTATION;
      }
      description "It specifies which sensor information shall be included in
        logged NR MDT and immediate NR MDT measurement if they are available.
        The following sensor measurement can be included or excluded for 
        the UE.";
      reference "Clause 5.10.29 of 3GPP TS 32.422";
    }
  }

  grouping UEMeasConfigGrp {
    description "Represents the UEMeasConfig dataType.
      This <<dataType>> defines the aconfiguration parameters of IOC TraceJob
        which are specific for UE level measurements collection.";
    
    leaf-list ueMeasurements {
      type string;
      description "It specifies the List of UE level measurements.";
    }

    leaf ueMeasGranularityPeriod {
      type uint32;
      description "It specifies the Granularity period used to produce UE level 
        measurements. The period is defined in milliseconds (ms).";
    }

    leaf-list nfTypeToMeasure {
      type string;
      description "It specifies the NF types to measure.";
    }    
    
    leaf-list objectInstances {
      type string;
      description "List of object instances.";
    }

    leaf-list rootObjectInstances {
      type string;
      description "List of root object instances.";
    }
  }

  grouping TraceJobGrp {

    leaf jobType {
      type enumeration {
        enum IMMEDIATE_MDT_ONLY;
        enum LOGGED_MDT_ONLY;
        enum TRACE_ONLY;
        enum IMMEDIATE_MDT_AND_TRACE;
        enum RLF_REPORT_ONLY;
        enum RCEF_REPORT_ONLY;
        enum LOGGED_MBSFN_MDT;
        enum 5GC_UE_LEVEL_MEASUREMENTS_ONLY;
        enum TRACE_AND_5GC_UE_LEVEL_MEASUREMENTS;
        enum IMMEDIATE_MDT_AND_5GC_UE_LEVEL_MEASUREMENTS;
        enum TRACE_AND_IMMEDIATE_MDT_AND_5GC_UE_LEVEL_MEASUREMENTS;      
      }
      default TRACE_ONLY;
      description "Specifies the MDT mode and it specifies also whether the
        TraceJob represents only MDT, Logged MBSFN MDT, Trace, or 5GC UE level measurement collection, or any combination 
        of Trace, immediate MDT and 5GC UE level measurement collection. 
        The attribute is applicable for Trace, MDT, RCEF and
        RLF reporting, and 5GC UE level measurement collection.";
      reference "Clause 5.9a of 3GPP TS 32.422 for additional details on the
        allowed values.";
    }

    
    list pLMNTarget {
      key "mcc mnc";
      description "Specifies which PLMN that the subscriber of the session to
        be recorded uses as selected PLMN. PLMN Target might differ from the
        PLMN specified in the Trace Reference";
      reference "Clause 5.9b of 3GPP TS 32.422";
      
      uses types3gpp:PLMNId;
    }

    leaf traceReportingConsumerUri {
      when '../traceReportingFormat  = "STREAMING"';
      type inet:uri;
      description "URI of the Streaming Trace data reporting MnS consumer
        (a.k.a. streaming target).
        This attribute shall be present if file based trace data reporting is
        supported and traceReportingFormat set to 'file based' or when
        jobType is set to Logged MDT or Logged MBSFN MDT.";
      reference "Clause 5.9 of 3GPP TS 32.422";
    }
    
    leaf traceCollectionEntityId  {
      when '../jobType = "LOGGED_MDT_ONLY" or ' 
        + '../jobType = "LOGGED_MBSFN_MDT"';
      type uint32;
      description "It specifies the TCE Id which is sent to the UE in 
        Logged MDT.";
      reference "Clause 5.10.11 of 3GPP TS 32.422";
    }

    list traceReference {        
      key "idx";
      min-elements 1;
      max-elements 1;
      description "A globally unique identifier, which uniquely identifies the
        Trace Session that is created by the TraceJob.
        In case of shared network, it is the MCC and MNC of the Participating
        Operator that request the trace session that shall be provided.
        The attribute is applicable for both Trace and MDT.";
      reference "Clause 5.6 of 3GPP TS 32.422";

      leaf idx { type uint32 ; }
      uses trace3gpp:TraceReferenceGrp ;    
    }

    leaf jobId {
      type string;
      yext3gpp:inVariant;
      description "Identifier of a TraceJob";
      yext3gpp:inVariant;
    }

    leaf traceReportingFormat {
      type enumeration {
        enum FILE_BASED;
        enum STREAMING;
      }
      default FILE_BASED;
      description "Specifies the trace reporting format - streaming trace
        reporting or file-based trace reporting";
      reference "3GPP TS 32.422 clause 5.11";
    }
    
    list traceTarget {
      key "targetIdType targetIdValue";
      max-elements 1;

      leaf targetIdType {
        type enumeration {
          enum IMSI;
          enum IMEI;
          enum IMEISV;
          enum PUBLIC_ID;
          enum UTRAN_CELL;
          enum E_UTRAN_CELL;
          enum NG_RAN_CELL;
          enum ENB;
          enum RNC;
          enum GNB;
          enum SUPI;
        }
      }

      leaf targetIdValue {
        type string;
      }

      description "Specifies the target object of the Trace and MDT. The
        attribute is applicable for both Trace and MDT. This attribute
        includes the ID type of the target as an enumeration and the ID value.

        The traceTarget shall be public ID in case of a Management Based
        Activation is done to an ScscfFunction. The traceTarget shall be
        cell only in case of the UTRAN cell traffic trace function.

        The traceTarget shall be E-UtranCell only in case of E-UTRAN cell
        traffic trace function.The traceTarget shall be either IMSI or
        IMEI(SV) if the Trace Session is activated to any of the following
        ManagedEntity(ies):
        - HssFunction
        - MscServerFunction
        - SgsnFunction
        - GgsnFunction
        - BmscFunction
        - RncFunction
        - MmeFunction

        The traceTarget shall be IMSI if the Trace Session is activated to a
        ManagedEntity playing a role of ServinGWFunction.

        In case of signaling based Trace/MDT, the traceTarget attribute shall 
        be able to carry (IMSI or IMEI(SV)or SUPI), the mDTAreaScope attribute 
        shall be able to carry a list of (cell or E-UtranCell or NRCellDU or 
        TA/LA/RA).

        In case of management based Immediate MDT, the traceTarget attribute
        shall be null value, the mDTAreaScope attribute shall carry a list of
        (Utrancell or E-UtranCell or NRCellDU).

        In case of management based Logged MDT, the traceTarget attribute
        shall carry an eBs or a RNC or gNBs. The Logged MDT should be initiated 
        on the specified eNB or RNC or gNB in traceTarget. The mDTAreaScope 
        attribute shall carry a list of (Utrancell or E-UtranCell or NRCellDU or 
        TA/LA/RA).

        In case of RLF reporting, or RCEF reporting,  the traceTarget 
        attribute shall be null value, the mDTAreaScope attribute shall carry 
        one or list of eNBs/gNBs";
      reference "3GPP TS 32.422";
    }

   list traceConfig {      
     when '../jobType = "TRACE_ONLY"'
     +  ' or ../jobType = "IMMEDIATE_MDT_AND_TRACE"'
     +  ' or ../jobType = "TRACE_AND_5GC_UE_LEVEL_MEASUREMENTS"'
     +  ' or ../jobType = "TRACE_AND_IMMEDIATE_MDT_AND_5GC_UE_LEVEL_MEASUREMENTS"';  
     key idx;
     description "Trace config";
     max-elements 1;
     uses TraceConfigGrp;    
     leaf idx { type string; }
    }
    
   list mdtConfig { 
     when '../jobType = "IMMEDIATE_MDT_ONLY"'
        + ' or ../jobType = "IMMEDIATE_MDT_AND_TRACE"'
        + ' or ../jobType = "RLF_REPORT_ONLY"'
        + ' or ../jobType = "RCEF_REPORT_ONLY"'
        + ' or ../jobType = "LOGGED_MBSFN_MDT"'
        + ' or ../jobType = "IMMEDIATE_MDT_AND_5GC_UE_LEVEL_MEASUREMENTS"'
        + ' or ../jobType = "TRACE_AND_IMMEDIATE_MDT_AND_5GC_UE_LEVEL_MEASUREMENTS"';
     key idx;
     description "MDT config";
     max-elements 1;       
     uses MdtConfigGrp;
     leaf idx { type string; }    
    }

   list ueMeasConfig { 
     when '../jobType = "5GC_UE_LEVEL_MEASUREMENTS_ONLY"'
        + ' or ../jobType = "TRACE_AND_5GC_UE_LEVEL_MEASUREMENTS"'
        + ' or ../jobType = "IMMEDIATE_MDT_AND_5GC_UE_LEVEL_MEASUREMENTS"'
        + ' or ../jobType = "TRACE_AND_IMMEDIATE_MDT_AND_5GC_UE_LEVEL_MEASUREMENTS"';
     key idx;
     description "5GC UE level measurements config";
     max-elements 1;       
     uses UEMeasConfigGrp;
     leaf idx { type string; }    
    }
    list nPNTarget {
      description "applicable only for NR and shall be present in case of NPN 
        either a PNI-NPN or a SNPN) and for management-based activation when 
        several NPNs are supported in the RAN.";
      key idx;
      max-elements 1;  
      uses NpnIdGrp;
      leaf idx { type string;}
    }
  }

  grouping TraceSubtree {
    description "Contains classes that manage Tracing.
      Should be used in all  classes (or classes inheriting from)
      - SubNnetwork
      - ManagedElement
      - ManagedFunction

      If a YANG module wants to augment these classes/list/groupings they must
      augment all user classes!";

    list TraceJob {
      description "A TraceJob instance represents the Trace Control and 
        Configuration parameters of a particular Trace Job (see TS 32.421 and 
        TS 32.422 for details). It can be name-contained by SubNetwork, 
        ManagedElement, ManagedFunction.

        To activate Trace Jobs, a MnS consumer has to create TraceJob object 
        instances on the MnS producer. A MnS consumer can activate a Trace Job 
        for another MnS consumer since it is not required the value of 
        traceCollectionEntityIPAddress or traceReportingConsumerUri to be 
        his own.

        For the details of Trace Job activation see clauses 4.1.1.1.2 and 
        4.1.2.1.2 of TS 32.422.

        When a MnS consumer wishes to deactivate a Trace Job, the MnS consumer 
        shall delete the corresponding TraceJob instance. 
        
        For details of management Trace Job activation/deactivation see clause
        4.1.1.1.2 of TS 32.422.

        The attribute traceReference specifies a globally unique ID and 
        identifies a Trace session. One Trace Session may be activated to 
        multiple Network Elements. The traceReference is populated by the
        consumer that makes the request for a Trace Session.

        The jobId attribute presents the job identifier of a TraceJob instance. 
        The jobId can be used to associate  multiple TraceJob instances. 
        For example, it is possible to configure the same jobId value for 
        multiple TraceJob instances required to produce the data (e.g. RSRP 
        values of M1 and RLF reports) for a specific network analysis.

        The attribute traceReportingFormat defines the method for reporting 
        the produced measurements. The selectable options are file-based or 
        stream-based reporting. In case of file-based reporting the attribute 
        traceCollectionEntityIPAddress is used to specify the IP address to 
        which the trace records shall be transferred, while in case of 
        stream-based reporting the attribute traceReportingConsumerUri 
        specifies the streaming target.

        The mandatory attribute traceTarget determines the target object of 
        the TraceJob. Dependent on the network element to which the Trace 
        Session is activated different types of the target object are possible. 
        The attribute pLMNTarget defines the PLMN for which sessions shall be 
        selected in the Trace Session in case of management based activation 
        when several PLMNs are supported in the RAN.

        The attribute jobType specifies the kind of data to collect. In case of
        Trace only, the configuration parameters of attribute traceConfig shall 
        be applied. In case of Immediate MDT only, Logged MDT only, RLF reports 
        only, RCEF reports only and Logged MBSFN MDT, the configuration parameters
        of attribute mdtConfig or a subset of these shall be applied. In case of 
        UE measurements only, the configuration parameters of attribute ueMeasConfig 
        shall be applied. In case of any combination of Trace, Immediate MDT, 
        Trace and UE measurements, the configuration parameters of the corresponding
        attributes traceConfig, mdtConfig and ueMeasConfig are applicable. 

        Creation and deletion of TraceJob instances by MnS consumers is 
        optional; when not supported, the TraceJob instances may be created 
        and deleted by the system or be pre-installed.";

      key id;
      uses top3gpp:Top_Grp ;
      container attributes {
        uses TraceJobGrp ;
      }
      uses files3gpp:FilesSubtree {
        if-feature FilesUnderTraceJob;
      }
    }
  }
}
